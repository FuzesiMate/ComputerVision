# Computer Vision Framework Requirements

# Specification: Specification Document
- Description: Requirements Document

## R23
Marker based object tracking

### R24
Marker detection

### R25
Store and forward marker positions

### R34
Assign markers to objects

## R1
Widely applicable

### R4
Easy-to-use configuration method

#### R5
Offline configuration

##### R12
Define objects and modules

###### R18
Set object and module specific parameters

###### R15
Automatically build the flow graph based on configuration

###### R19
Validate configuration

#### R6
Online configuration

##### R13
Set frame provider parameters runtime

##### R14
Set image processing specific parameters runtime

### R16
Provide raw image processing data

### R17
Provide object and marker mapped data based on configuration

### R20
Handle any kind of frame source

#### R28
Read from video file(s)

#### R29
Capture from camera(s)

### R21
Handle multi-camera systems

### R26
Several marker types can be detected at the same time

### R27
Object detection limit can be set

### R30
Distributed usage

#### R31
Send output data over network interface

## R2
Ready-to-use

### R7
Built-in marker tracking methods

### R22
Built-in 2D-3D transformation

### R35
Built-in frame provider

## R3
Easily extensible

### R8
Integrate new marker tracking algorithm

#### R10
Well defined image processor interface

### R9
Integrate new data sender method

#### R11
Well defined data sender interface

### R32
Integrate new frame source

#### R33
Well defined frame source interface

### R36
Integrate new visualizer method
